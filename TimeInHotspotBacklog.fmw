FME workspace TimeInHotspotBacklog.fmw

Parameters:
- DestDataset_GEODATABASE_FILE = D:\Crime\TimeInHotspot.gdb   # Destination ESRI Geodatabase (File-based) File
- DestDataset_XLS_ADO = D:\Crime\TimeInHotspots.xlsx   # Destination Microsoft Excel File
- SourceDataset_GEODATABASE_SDE = police_sde_prod   # Source ESRI Geodatabase (ArcSDE) Dataset
- SourceDataset_FILEGDB = D:\Crime\TimeInHotspot.gdb   # *.gdb Source Geodatabase

Readers:
- GEODATABASE_SDE_1: GEODATABASE_SDE from $(SourceDataset_GEODATABASE_SDE)
- FILEGDB_1: FILEGDB from $(SourceDataset_FILEGDB)

Writers:
- GEODATABASE_FILE_1: GEODATABASE_FILE to $(DestDataset_GEODATABASE_FILE)
- XLS_ADO_1: XLS_ADO to $(DestDataset_XLS_ADO)

Note: This week's records / Friday to Thursday
Week1019_1021 (reader FILEGDB_1)
    attributes: OBJECTID objectid, szIpAddress text(15), dtTimeStamp date, szPriId text(15), szSecId text(15), rLatitude double, rLongitude double, iSpeed smallint, iHeading smallint, byStatus smallint
    -> Tester
Note: Last Thursday
XYARC_10182012 (reader FILEGDB_1)
    attributes: OBJECTID objectid, szIpAddress text(15), dtTimeStamp date, szPriId text(15), szSecId text(15), rLatitude double, rLongitude double, iSpeed smallint, iHeading smallint, byStatus smallint
    -> Tester
Note: Throw out 0,0 locations
Tester
    TEST_DESCRIPTION = ""
    TEST_CLAUSE = TEST "@Value(rLatitude)" > "0"
    BOOL_OP = AND
    TEST_MODE = Automatic
    PASSED -> Reprojector
Note: State Plane Missouri East Feet
Reprojector
    DEST = MO83-EF
    SOURCE = Read from feature
    RASTER_CELL_SIZE = Preserve Cells
    INTERPOLATION_TYPE_NAME = Nearest Neighbor
    STROKE_ARCS = Yes
    REPROJECTED -> Sorter
Sorter
    SORT_PARM = szPriId ALPHA ASCENDING dtTimeStamp NUMERIC DESCENDING
    SORTED -> AttributeCreator_3
Note: Time Attributes
Note: Day of Week / Hour of Day / epoch / _ totaltime
AttributeCreator_3
    ATTR_LIST = DayOfWeek,fme_basicstring:19:@Value(dtTimeStamp),HourOfDay,fme_basicstring:19:@Value(dtTimeStamp),_totaltime,0,epoch,@Value(dtTimeStamp)
    -> DateFormatter_2
Note: Set Day of Week
DateFormatter_2
    FMT = %a
    DATE_ATTR = DayOfWeek
    -> DateFormatter_3
Note: Set Hour of Day
DateFormatter_3
    FMT = %H
    DATE_ATTR = HourOfDay
    -> DateFormatter
Note: Set epoch (seconds)
DateFormatter
    FMT = %s
    DATE_ATTR = epoch
    -> AttributeExposer
Note: Expose fme_feature_type
AttributeExposer
    ATTR_LIST = fme_feature_type
    -> VariableRetriever
Note: Set _prevcar = LastCar
VariableRetriever
    SCOPE = Global
    VALUE_ATTR = _prevcar
    VARNAME = LastCar
    -> VariableRetriever_2
Note: Set _seconds = LastEpoch
VariableRetriever_2
    SCOPE = Global
    VALUE_ATTR = _epoch
    VARNAME = LastEpoch
    -> Tester_2
Note: Compare _prevcar to current car
Tester_2
    TEST_DESCRIPTION = ""
    TEST_CLAUSE = TEST "@Value(_prevcar)" = "@Value(szPriId)"
    BOOL_OP = OR
    TEST_MODE = Automatic
    PASSED -> ExpressionEvaluator
    FAILED -> ExpressionEvaluator_2
Note: If same car, set _totaltime to last time stamp - this time stamp
ExpressionEvaluator
    EXPRESSION = @Value(_epoch) - @Value(epoch)
    VAL_ATTR = _totaltime
    -> VariableSetter
Note: If new car, reset _totaltime to 0
ExpressionEvaluator_2
    EXPRESSION = 0
    VAL_ATTR = _totaltime
    -> VariableSetter
Note: Store vehicle id in LastCar
VariableSetter
    VALUE = @Value(szPriId)
    SCOPE = Global
    VARNAME = LastCar
    -> VariableSetter_2
Note: Store epoch in LastEpoch
VariableSetter_2
    VALUE = @Value(epoch)
    SCOPE = Global
    VARNAME = LastEpoch
    -> Tester_4
Note: Use fme_feature_type to throw out records from last week
Tester_4
    TEST_DESCRIPTION = ""
    TEST_CLAUSE = TEST "@Value(fme_feature_type)" LIKE "Week%"
    BOOL_OP = OR
    TEST_MODE = Automatic
    PASSED -> SpatialFilter [input 2]
yourid.AVLHotspots (reader GEODATABASE_SDE_1)
    attributes: geodb_oid integer, OBJECTID_1 integer, OBJECTID integer, Incidents integer, SOURCE_ID integer, CountNorma double, LivingUnit double, Subdivisio char(40), NAME char(10), CODE smallint, Addresses integer, PossibleBu integer, Exclude smallint, EditStatus smallint, Shape_Leng double, EditorName char(10), ID smallint, B_Incid integer, B_Unit integer, B_Area double, UniqueAdd integer, Structures integer, TimeOfDay double, Incid2012 integer, IncidRatio double, PeteDanger smallint, Pete_Dange double, Precinct char(8), created_user char(255), created_date date,
      last_edited_user char(255), last_edited_date date, Shape.area double, Shape.len double
    -> SpatialFilter [input 1]
SpatialFilter
    USE_BOUNDING_BOX = No
    PREDATTR = _predicate
    BASE_TYPE = Bases First
    PREDICATES = INTERSECTS
    MERGE_ATTRS = Yes
    PASS_CRITERIA = Pass Against One Base
    CURVE_BOUNDARY_RULE_PARAM = Default Rule
    PASSED -> Sorter_2
Note: Sort by Hotspot
Sorter_2
    SORT_PARM = ID NUMERIC ASCENDING
    SORTED -> Tester_3
Note: Throw out any records > 60 minutes
Tester_3
    TEST_DESCRIPTION = ""
    TEST_CLAUSE = TEST "@Value(_totaltime)" < "3600"
    BOOL_OP = OR
    TEST_MODE = Automatic
    PASSED -> AttributeKeeper
AttributeKeeper
    KEEP_ATTRS = OBJECTID,ID,dtTimeStamp,szPriId,DayOfWeek,HourOfDay,_totaltime,fme_feature_type
    -> AggregateByHotspot
    -> AggregateByDayOfWeek
    -> AggregateByHourOfDay
    -> CreateFileName
AggregateByHotspot: Aggregator
    ACCUM_ATTRS_NAME = Yes
    GROUP_BY = ID
    SEP = ,
    ORDERED = No
    CONTAIN_INDIVID_GEOMS = No
    SUM = _totaltime
    COUNT_ATTR = _count
    AGGREGATE -> ByCar (writer GEODATABASE_FILE_1)
    AGGREGATE -> ByHotSpot (writer XLS_ADO_1)
ByCar (writer GEODATABASE_FILE_1)
    attributes: szPrId char(50), TotalTime integer
ByHotSpot (writer XLS_ADO_1)
    attributes: HotspotID double, TotalTime double
AggregateByDayOfWeek: Aggregator
    ACCUM_ATTRS_NAME = Yes
    GROUP_BY = ID DayOfWeek
    SEP = ,
    ORDERED = No
    CONTAIN_INDIVID_GEOMS = No
    SUM = _totaltime
    AGGREGATE -> Sorter_3
Sorter_3
    SORT_PARM = ID NUMERIC ASCENDING DayOfWeek ALPHA ASCENDING
    SORTED -> ByDayOfWeek (writer XLS_ADO_1)
ByDayOfWeek (writer XLS_ADO_1)
    attributes: HotSpotID decimal(20,10), Time double, DayOfWeek varchar(20)
AggregateByHourOfDay: Aggregator
    ACCUM_ATTRS_NAME = Yes
    GROUP_BY = ID HourOfDay
    SEP = ,
    ORDERED = No
    CONTAIN_INDIVID_GEOMS = No
    SUM = _totaltime
    AGGREGATE -> Sorter_4
Sorter_4
    SORT_PARM = ID NUMERIC ASCENDING HourOfDay NUMERIC ASCENDING
    SORTED -> ByHourOfDay (writer XLS_ADO_1)
ByHourOfDay (writer XLS_ADO_1)
    attributes: HotSpotID decimal(20,10), HourOfDay varchar(20), Time double
CreateFileName: AttributeCreator
    ATTR_LIST = _file_name,fme_basicstring:24:@Value(fme_feature_type)
    -> ReplaceWeekWithPings
ReplaceWeekWithPings: StringReplacer
    FIND_TEXT = Week
    SRC_ATTRS = _file_name
    REPLACE_TEXT = Pings
    REGEXP = no
    CASE = no
    -> TimePerHit (writer GEODATABASE_FILE_1)
TimePerHit (writer GEODATABASE_FILE_1)
    attributes: szPriID char(20), HotspotID integer, dtTimeStamp date, DayOfWeek char(20), HourOfDay char(20), TotalTime integer
